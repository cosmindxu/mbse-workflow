package LA {
        #prompt part laGuidance {
            doc /* LA: decompose the system into logical components. Every logical function traces to a system function; components exchange through ports; nothing physical is decided yet. */
        }

        // ---- mainComponent's mode/status/configuration state definitions ----
        #Mode state def SwarmMode {
            doc /* the fleet-level watch mode of the system: normal coverage, or a share of the mesh links between members jammed. Restates SA::SurveillanceDroneSwarmMode at LA, tagged #Mode per this run's modes-and-states option. */
            initial start;
            state Covering {
                doc /* the fleet is holding continuous watch over the tasked area under normal mesh conditions. */
            }
            state MeshDegraded {
                doc /* a share of the links between drones is jammed; the brief's named fleet mode. */
            }
            transition start -> Covering;
            transition Covering -> MeshDegraded;
            transition MeshDegraded -> Covering;
        }
        #Configuration state def FleetConfiguration {
            doc /* the same fleet-level watch condition as SwarmMode, restated as a #Configuration state def per CV-16's rule that fleet-level states belong to that kind rather than #Mode; deliberately redundant with SwarmMode so both this run's option and CV-16 are satisfied. */
            initial start;
            state Covering {
                doc /* the fleet is holding continuous watch over the tasked area under normal mesh conditions. */
            }
            state MeshDegraded {
                doc /* a share of the links between drones is jammed; the brief's named fleet mode. */
            }
            transition start -> Covering;
            transition Covering -> MeshDegraded;
            transition MeshDegraded -> Covering;
        }
        #State state def SwarmStatus {
            doc /* the coarse operating status of the system as a whole, independent of its watch mode. Restates SA::SurveillanceDroneSwarmStatus at LA. */
            initial start;
            state Idle {
                doc /* the system has no active mission tasking. */
            }
            state Tasked {
                doc /* the system has received mission tasking and is conducting the watch. */
            }
            transition start -> Idle;
            transition Idle -> Tasked;
            transition Tasked -> Idle;
        }

        // the system, to be decomposed into logical components (next step)
        part def SurveillanceDroneSwarmLogical {
            in port taskingIn : SA::SurveillanceDroneSwarmSystem::taskingIn;
            out port reportsOut : SA::SurveillanceDroneSwarmSystem::reportsOut;
            out port decisionsOut : SA::SurveillanceDroneSwarmSystem::decisionsOut;
            in port supervisionIn : SA::SurveillanceDroneSwarmSystem::supervisionIn;
            in port recallIn : SA::SurveillanceDroneSwarmSystem::recallIn;
            in port ackIn : SA::SurveillanceDroneSwarmSystem::ackIn;
            out port statusOut : SA::SurveillanceDroneSwarmSystem::statusOut;
            out port rechargeRequestOut : SA::SurveillanceDroneSwarmSystem::rechargeRequestOut;

            state mode : SwarmMode;
            state configuration : FleetConfiguration;
            state status : SwarmStatus;

            #Estimate attribute areaUnderWatchShare :> Common::areaUnderWatchShare = 0.92 {
                doc /* worst-case estimate; basis: FleetOfTwelveDrones rotating through sectors and recharge under redistributeCoverage/rotateRecharge keeps a standing majority of sectors watched; target >= 0.9. */
            }
            #Estimate attribute coverageLossOnMemberLoss :> Common::coverageLossOnMemberLoss = 0.2 {
                doc /* worst-case estimate; basis: losing 1 of 12 members costs roughly 1/12 of coverage before redistributeCoverage re-spreads the remaining fleet, plus handover lag; target <= 0.25. */
            }
            #Estimate attribute jammedMeshAreaUnderWatchShare :> Common::jammedMeshAreaUnderWatchShare = 0.78 {
                doc /* worst-case estimate; basis: relayLink lets members reach isolated peers through surviving links when half the mesh is jammed, at some coverage cost; target >= 0.75. */
            }
            #Estimate attribute groundLinkLossAreaUnderWatchShare :> Common::groundLinkLossAreaUnderWatchShare = 0.9 {
                doc /* worst-case estimate; basis: the eight #Coordination functions (handOverSector, rotateRecharge, redistributeCoverage, deconflictMembers, relayLink, correlateTracks, handOverTrack, admitMember) run over MeshRadio, independent of GroundLinkRadio, so coverage should hold when the ground link is down; where they end up allocated is next step's decision and would revise this figure. Target >= 0.9. */
            }
            #Estimate attribute watchEnduranceHours :> Common::watchEnduranceHours = 30 {
                doc /* worst-case estimate; basis: 40-minute sorties against a 60-minute recharge, rotated across 12 members via rotateRecharge, sustains the watch well past a duty shift before ground-crew fatigue becomes the limit; target >= 24 h. */
            }
            #Estimate attribute reportLatencySeconds :> Common::reportLatencySeconds = 45 {
                doc /* worst-case estimate; basis: onboard detection, correlateTracks de-duplication and reportDetections triage add delay before GroundLinkRadio delivery; target <= 60 s. */
            }
            #Estimate attribute positionErrorWithoutGnssMeters :> Common::positionErrorWithoutGnssMeters = 40 {
                doc /* worst-case estimate; basis: navigateAgainstStoredMaps bounds drift by matching camera views to StoredMaps over a 10-minute GNSS outage; target <= 50 m. */
            }
            #Estimate attribute reportHoldMinutes :> Common::reportHoldMinutes = 35 {
                doc /* worst-case estimate; basis: reportDetections buffers reports on a cut-off member with margin above the brief's floor; target >= 30 min. */
            }
            #Estimate attribute reportsLostInLinkGap :> Common::reportsLostInLinkGap = 0 {
                doc /* worst-case estimate; basis: reportDetections holds reports rather than dropping them across a ground-link gap and delivers them once the link returns; target <= 0. */
            }
            #Estimate attribute missedDetectionShare :> Common::missedDetectionShare = 0.08 {
                doc /* worst-case estimate; basis: detectAndClassifyObjects under nominal sensing and continuous watch; target <= 0.1. */
            }
            #Estimate attribute falseAlarmsPerHour :> Common::falseAlarmsPerHour = 1.5 {
                doc /* worst-case estimate; basis: reportDetections triage and manageClassifierVersion consistency hold false alarms under the brief's cap; target <= 2 / h. */
            }
            #Estimate attribute operatorAlertsPerHour :> Common::operatorAlertsPerHour = 18 {
                doc /* worst-case estimate; basis: reportDetections triage and de-duplication keep the alert rate under the operator's 20/h judging limit, with margin; target <= 20 / h. */
            }
            #Estimate attribute acknowledgedReportsThatMatterShare :> Common::acknowledgedReportsThatMatterShare = 0.82 {
                doc /* worst-case estimate; basis: commandSupervision's reporting threshold plus reportDetections triage push relevance above the brief's floor; target >= 0.8. */
            }
            #Estimate attribute onboardClassificationCostUsd :> Common::onboardClassificationCostUsd = 280 {
                doc /* worst-case estimate; basis: manageClassifierVersion keeps one classifier version so no per-member duplicate compute spend is needed, staying under ComputingCostCap; target <= 300 USD. */
            }

            doc /* the system's logical placeholder: one component carrying every LA function this step, its ports mirrored from SA. The decomposition of this component into distinct logical components (sensing, navigation, coordination, reporting) is the next step's job, done several ways and compared; this step fixes the population's structure, its modes and states, the hazards it makes visible and the architecture's worst-case measures of effectiveness. */
        }

        // ---- member mode/status state definitions (CV-18/CV-19, carried from SA) ----
        #Mode state def SurveillanceDroneMode {
            doc /* the operating mode of one member drone: nominal watching, the degraded and constrained conditions the brief names, and landed. Restates SA::SurveillanceDroneMode at LA and carries its four rule properties. */
            initial start;
            state Landed {
                doc /* grounded, not watching: recalled, out of cleared airspace, quarantined, or recharging. */
            }
            state Watching {
                doc /* actively holding assigned sector watch under normal conditions. */
            }
            state NavigationDegraded {
                doc /* no satellite positioning; navigating by matching camera views against stored maps. */
            }
            state SensingDegraded {
                doc /* this drone's sensors cannot be trusted as they are. */
            }
            state Isolated {
                doc /* cut off from the other drones. */
            }
            state Quarantined {
                doc /* failed admission; takes no part in coordination until readmitted. */
            }
            state Recalled {
                doc /* under a recall-and-land order; no longer watching, heading to land. */
            }
            state OutsideClearedAirspace {
                doc /* outside the airspace authority's cleared limits; no longer watching, heading to land. */
            }
            transition start -> Landed;
            transition Landed -> Watching;
            transition Watching -> NavigationDegraded;
            transition NavigationDegraded -> Watching;
            transition Watching -> SensingDegraded;
            transition SensingDegraded -> Watching;
            transition Watching -> Isolated;
            transition Isolated -> Watching;
            transition Isolated -> Landed;
            transition Landed -> Quarantined;
            transition Quarantined -> Landed;
            transition Watching -> Recalled;
            transition Recalled -> Landed;
            transition Watching -> OutsideClearedAirspace;
            transition OutsideClearedAirspace -> Landed;

            @SysproseVerification::PropertyPattern {
                doc /* RecallWins: once a drone is recalled, it does not watch again until it has landed. */
                attribute pattern = "absence";
                attribute scope = "between";
                attribute q = "state Recalled";
                attribute r = "state Landed";
                attribute p = "state Watching";
            }
            @SysproseVerification::PropertyPattern {
                doc /* ReturnsWhenIsolated: from any situation a drone can be in, it can always get back to landed; an isolated drone included. */
                attribute pattern = "recovery";
                attribute scope = "globally";
                attribute p = "state Landed";
            }
            @SysproseVerification::PropertyPattern {
                doc /* GeofenceBreachEndsWatch: once a drone is outside its cleared airspace, it does not watch until it has landed. */
                attribute pattern = "absence";
                attribute scope = "between";
                attribute q = "state OutsideClearedAirspace";
                attribute r = "state Landed";
                attribute p = "state Watching";
            }
            @SysproseVerification::PropertyPattern {
                doc /* QuarantinedStaysOut: once a drone is quarantined, it takes no part in coordination until it has been readmitted. */
                attribute pattern = "absence";
                attribute scope = "between";
                attribute q = "state Quarantined";
                attribute r = "state Landed";
                attribute p = "state Watching";
            }
        }
        #State state def SurveillanceDroneStatus {
            doc /* the coarse platform status of one member drone, independent of its watch mode. Restates SA::SurveillanceDroneStatus at LA. */
            initial start;
            state Idle {
                doc /* on the ground, available but not tasked. */
            }
            state Active {
                doc /* airborne and performing tasked activity. */
            }
            state Recharging {
                doc /* at a recharge point being serviced by the ground crew. */
            }
            transition start -> Idle;
            transition Idle -> Active;
            transition Active -> Recharging;
            transition Recharging -> Idle;
            transition Active -> Idle;
        }

        // the population's replicable member definition (CV-16). Functions-only at this step (layer.functionsOnly): the fleet usage, its representative peers and the peer interface between them are instantiated in the next step's component decomposition, several ways, and compared -- this step keeps every function allocated to the placeholder mainComponent, so no #Coordination/#C2 function is lost in the meantime.
        #prose part fleetFact {
            doc /* Population: 12 members of SurveillanceDrone. Carried from the brief; the #Member part def SurveillanceDrone above declares the replicable element and its peer mesh ports. Per this step's functions-only rule, the fleet usage, its representative pair and the Common::MeshLink peer interface between them are instantiated in the next step's component decomposition rather than here; every function stays allocated to mainComponent in this fragment. */
        }

        // actors, carried over unchanged
        #Actor part def DutyController {
            out port supervisionOut : SA::DutyController::supervisionOut;
            out port recallOut : SA::DutyController::recallOut;
            out port ackOut : SA::DutyController::ackOut;
            in port statusIn : SA::DutyController::statusIn;
            doc /* the single operator at the operations centre who tasks, supervises and recalls the swarm and acknowledges its reports; ports carried unchanged from SA. */
        }
        part dutyController : DutyController;
        trace dutyController to SurveillanceDroneSwarm::SA::dutyController;
        #Actor part def Analysts {
            doc /* operations centre staff who judge the merged, triaged reports and tracks the operations centre produces; no direct port exchange with the system, carried unchanged from SA. */
        }
        part analysts : Analysts;
        trace analysts to SurveillanceDroneSwarm::SA::analysts;
        #Actor part def OperationsCentre {
            out port taskingOut : SA::OperationsCentre::taskingOut;
            in port reportsIn : SA::OperationsCentre::reportsIn;
            in port decisionsIn : SA::OperationsCentre::decisionsIn;
            doc /* commissions surveillance missions, tasks the system with the area of interest and mission window, and takes in its triaged reports and decision records; ports carried unchanged from SA. */
        }
        part operationsCentre : OperationsCentre;
        trace operationsCentre to SurveillanceDroneSwarm::SA::operationsCentre;
        #Actor part def AirspaceAuthority {
            doc /* says when and where the drones may fly; constrains cleared airspace as a limit the members' rules never breach, with no direct port exchange with the system, carried unchanged from SA. */
        }
        part airspaceAuthority : AirspaceAuthority;
        trace airspaceAuthority to SurveillanceDroneSwarm::SA::airspaceAuthority;
        #Actor part def GroundCrew {
            in port rechargeIn : SA::GroundCrew::rechargeIn;
            doc /* services and recharges the drones between sorties, taking in recharge-slot requests; ports carried unchanged from SA. */
        }
        part groundCrew : GroundCrew;
        trace groundCrew to SurveillanceDroneSwarm::SA::groundCrew;
        #Actor part def FixedCameraNetworkOwner {
            doc /* runs the existing camera network and supplies its tracks to the operations centre for merging with the system's tracks; exchanges with the operations centre, not with the system directly, carried unchanged from SA. */
        }
        part fixedCameraNetworkOwner : FixedCameraNetworkOwner;
        trace fixedCameraNetworkOwner to SurveillanceDroneSwarm::SA::fixedCameraNetworkOwner;
        #Actor part def ProgrammeSponsor {
            doc /* pays for the fleet and holds the per-drone computing cost cap; a budget stakeholder with no operational data exchange with the system, carried unchanged from SA. */
        }
        part programmeSponsor : ProgrammeSponsor;
        trace programmeSponsor to SurveillanceDroneSwarm::SA::programmeSponsor;

        // functions, carried over from SA: every one of them has to be realised here
        action def HoldSectorWatch {
            doc /* holding sector watch is the fleet's baseline activity: a member watches its assigned sector, coordinated with peers via handOverSector; realised here as a system-level function on mainComponent pending allocation to a sensing/flight-control logical component next step. */
        }
        action def DetectAndClassifyObjects {
            doc /* detecting and classifying moving objects is performed onboard against the single classifier version manageClassifierVersion keeps current; realised here as a system-level function pending allocation to a perception logical component next step. */
        }
        action def NavigateAgainstStoredMaps {
            doc /* navigation without satellite positioning matches a member's camera view against StoredMaps reference imagery; realised here as a system-level function pending allocation to a navigation logical component next step. */
        }
        action def ReportDetections {
            doc /* triages and de-duplicates member detections into DetectionReportsAndTracks for the operations centre, holding them across a link gap and taking in acknowledgement; realised here as a system-level function pending allocation to a reporting logical component next step. */
        }
        action def RecordDecision {
            doc /* keeps the decision record for every report sent -- its frames, classifier version, reporting threshold and acknowledger; realised here as a system-level function pending allocation to a reporting logical component next step. */
        }
        action def PresentStatusPicture {
            doc /* aggregates each member's position, activity, coverage and degradation into StatusPicture for the duty controller; a command-and-control function realised at system level here, kept ground-facing this step. */
        }
        action def TaskMission {
            doc /* takes in the area of interest, its sectors and the mission window from the operations centre; a command-and-control function realised at system level here, kept ground-facing this step. */
        }
        action def CommandSupervision {
            doc /* takes in priorities, a sector to look at more closely, and the reporting threshold from the duty controller; a command-and-control function realised at system level here, kept ground-facing this step. */
        }
        action def RecallAndLand {
            doc /* takes in recall-and-land for the whole fleet or one member and ends that member's watch until it has landed; a command-and-control function realised at system level here, kept ground-facing this step. */
        }
        action def AcknowledgeReport {
            doc /* takes in the duty controller's acknowledgement of a detection report; a command-and-control function realised at system level here, kept ground-facing this step. */
        }
        action def HandOverSector {
            doc /* hands a sector's watch from one member to a peer, over the mesh, before the first must leave station; a coordination function realised at system level here, mitigating a gap on recall or recharge departure. */
        }
        action def RotateRecharge {
            doc /* negotiates recharge rotation between members and with the ground crew so watch continuity is kept; a coordination function realised at system level here. */
        }
        action def RedistributeCoverage {
            doc /* redistributes coverage across the fleet when a member is lost or added; a coordination function realised at system level here, the main lever for holding coverage despite membership change. */
        }
        action def DeconflictMembers {
            doc /* deconflicts flight paths between members sharing the same airspace, over the mesh; a coordination function realised at system level here. */
        }
        action def RelayLink {
            doc /* relays mesh traffic for a member that is otherwise out of reach; a coordination function realised at system level here, and the main lever for coordination continuity when the ground link is down or the mesh is jammed. */
        }
        action def CorrelateTracks {
            doc /* correlates one member's tracks against a peer's before reporting, to avoid duplicate and stale tracks; a coordination function realised at system level here. */
        }
        action def HandOverTrack {
            doc /* hands a track from a member that can no longer see the object to a peer that can, over the mesh; a coordination function realised at system level here. */
        }
        action def AdmitMember {
            doc /* admits, or refuses, a member's request to join the mesh and take part in coordination, guarding against a device that is not one of the fleet; a coordination function realised at system level here. */
        }
        action def ManageClassifierVersionFunction {
            doc /* keeps one classifier version across the fleet and knows which version each member runs, so members do not classify the same object differently; realised at system level here. */
        }
        action def MergeWithCameraNetworkTracks {
            doc /* merges the fleet's reports, tracks and decision records with the fixed camera network's tracks; performed by the operations centre actor, unchanged from SA. */
        }
        action def ViewStatusPicture {
            doc /* takes in the status picture contributed by each member; performed by the duty controller actor, unchanged from SA. */
        }
        action def ServiceAndRecharge {
            doc /* recharges and services a drone that has come in to land, about 60 minutes; performed by the ground crew actor, unchanged from SA. */
        }
        action def ProvideCameraTracks {
            doc /* supplies tracks from the fixed camera network to the operations centre for merging; performed by the fixed camera network owner actor, unchanged from SA. */
        }
        action def JudgeAlerts {
            doc /* judges the merged, triaged reports and tracks to decide which alerts matter; performed by the analysts actor, unchanged from SA. */
        }
        action holdSectorWatch : HoldSectorWatch;
        trace holdSectorWatch to SurveillanceDroneSwarm::SA::holdSectorWatch;
        action detectAndClassifyObjects : DetectAndClassifyObjects;
        trace detectAndClassifyObjects to SurveillanceDroneSwarm::SA::detectAndClassifyObjects;
        action navigateAgainstStoredMaps : NavigateAgainstStoredMaps;
        trace navigateAgainstStoredMaps to SurveillanceDroneSwarm::SA::navigateAgainstStoredMaps;
        action reportDetections : ReportDetections {
            out reportsOut : Common::DetectionReportsAndTracks;
            in ackIn : Common::ReportAcknowledgements;
        }
        trace reportDetections to SurveillanceDroneSwarm::SA::reportDetections;
        action recordDecision : RecordDecision {
            out decisionsOut : Common::DecisionRecords;
        }
        trace recordDecision to SurveillanceDroneSwarm::SA::recordDecision;
        #C2 action presentStatusPicture : PresentStatusPicture {
            out statusOut : Common::StatusPicture;
        }
        trace presentStatusPicture to SurveillanceDroneSwarm::SA::presentStatusPicture;
        #C2 action taskMission : TaskMission {
            in taskingIn : Common::MissionTasking;
        }
        trace taskMission to SurveillanceDroneSwarm::SA::taskMission;
        #C2 action commandSupervision : CommandSupervision {
            in supervisionIn : Common::SupervisoryAndRecallCommands;
        }
        trace commandSupervision to SurveillanceDroneSwarm::SA::commandSupervision;
        #C2 action recallAndLand : RecallAndLand {
            in recallIn : Common::SupervisoryAndRecallCommands;
        }
        trace recallAndLand to SurveillanceDroneSwarm::SA::recallAndLand;
        #C2 action acknowledgeReport : AcknowledgeReport {
            in ackIn : Common::ReportAcknowledgements;
        }
        trace acknowledgeReport to SurveillanceDroneSwarm::SA::acknowledgeReport;
        #Coordination action handOverSector : HandOverSector {
            out msgOut : Common::CoordinationMessage;
            in msgIn : Common::CoordinationMessage;
        }
        trace handOverSector to SurveillanceDroneSwarm::SA::handOverSector;
        #Coordination action rotateRecharge : RotateRecharge {
            out msgOut : Common::CoordinationMessage;
            in msgIn : Common::CoordinationMessage;
        }
        trace rotateRecharge to SurveillanceDroneSwarm::SA::rotateRecharge;
        #Coordination action redistributeCoverage : RedistributeCoverage {
            out msgOut : Common::CoordinationMessage;
            in msgIn : Common::CoordinationMessage;
        }
        trace redistributeCoverage to SurveillanceDroneSwarm::SA::redistributeCoverage;
        #Coordination action deconflictMembers : DeconflictMembers {
            out msgOut : Common::CoordinationMessage;
            in msgIn : Common::CoordinationMessage;
        }
        trace deconflictMembers to SurveillanceDroneSwarm::SA::deconflictMembers;
        #Coordination action relayLink : RelayLink {
            in msgIn : Common::CoordinationMessage;
            out msgOut : Common::CoordinationMessage;
        }
        trace relayLink to SurveillanceDroneSwarm::SA::relayLink;
        #Coordination action correlateTracks : CorrelateTracks {
            in trackIn : Common::Track;
            out trackOut : Common::Track;
        }
        trace correlateTracks to SurveillanceDroneSwarm::SA::correlateTracks;
        #Coordination action handOverTrack : HandOverTrack {
            in trackIn : Common::Track;
            out trackOut : Common::Track;
        }
        trace handOverTrack to SurveillanceDroneSwarm::SA::handOverTrack;
        #Coordination action admitMember : AdmitMember {
            in msgIn : Common::CoordinationMessage;
            out msgOut : Common::CoordinationMessage;
        }
        trace admitMember to SurveillanceDroneSwarm::SA::admitMember;
        action manageClassifierVersion : ManageClassifierVersionFunction;
        trace manageClassifierVersion to SurveillanceDroneSwarm::SA::manageClassifierVersion;
        #C2 action taskMissionAct : TaskMission {
            out taskingOutA : Common::MissionTasking;
            out taskingOutB : Common::MissionTasking;
        }
        allocate taskMissionAct to operationsCentre;
        trace taskMissionAct to SurveillanceDroneSwarm::SA::taskMissionAct;
        action mergeAct : MergeWithCameraNetworkTracks {
            in swarmReportsInA : Common::DetectionReportsAndTracks;
            in swarmReportsInB : Common::DetectionReportsAndTracks;
            in decisionRecordsInA : Common::DecisionRecords;
            in decisionRecordsInB : Common::DecisionRecords;
            in cameraTracksIn : Common::CameraNetworkTracks;
            out mergedOut : Common::DetectionReportsAndTracks;
        }
        allocate mergeAct to operationsCentre;
        trace mergeAct to SurveillanceDroneSwarm::SA::mergeAct;
        #C2 action commandSupervisionAct : CommandSupervision {
            out supervisionOutA : Common::SupervisoryAndRecallCommands;
            out supervisionOutB : Common::SupervisoryAndRecallCommands;
        }
        allocate commandSupervisionAct to dutyController;
        trace commandSupervisionAct to SurveillanceDroneSwarm::SA::commandSupervisionAct;
        #C2 action recallAndLandAct : RecallAndLand {
            out recallOutA : Common::SupervisoryAndRecallCommands;
            out recallOutB : Common::SupervisoryAndRecallCommands;
        }
        allocate recallAndLandAct to dutyController;
        trace recallAndLandAct to SurveillanceDroneSwarm::SA::recallAndLandAct;
        #C2 action acknowledgeReportAct : AcknowledgeReport {
            out ackOut : Common::ReportAcknowledgements;
        }
        allocate acknowledgeReportAct to dutyController;
        trace acknowledgeReportAct to SurveillanceDroneSwarm::SA::acknowledgeReportAct;
        action viewStatusAct : ViewStatusPicture {
            in statusInA : Common::StatusPicture;
            in statusInB : Common::StatusPicture;
        }
        allocate viewStatusAct to dutyController;
        trace viewStatusAct to SurveillanceDroneSwarm::SA::viewStatusAct;
        action serviceAndRechargeAct : ServiceAndRecharge {
            in rechargeIn : Common::CoordinationMessage;
        }
        allocate serviceAndRechargeAct to groundCrew;
        trace serviceAndRechargeAct to SurveillanceDroneSwarm::SA::serviceAndRechargeAct;
        action provideCameraTracksAct : ProvideCameraTracks {
            out cameraTracksOut : Common::CameraNetworkTracks;
        }
        allocate provideCameraTracksAct to fixedCameraNetworkOwner;
        trace provideCameraTracksAct to SurveillanceDroneSwarm::SA::provideCameraTracksAct;
        action judgeAlertsAct : JudgeAlerts {
            in mergedIn : Common::DetectionReportsAndTracks;
        }
        allocate judgeAlertsAct to analysts;
        trace judgeAlertsAct to SurveillanceDroneSwarm::SA::judgeAlertsAct;

        // interactions, carried over as functional exchanges
        flow taskingToAFlow of Common::MissionTasking from taskMissionAct::taskingOutA to taskMission::taskingIn;
        flow taskingToBFlow of Common::MissionTasking from taskMissionAct::taskingOutB to taskMission::taskingIn;
        flow supervisionToAFlow of Common::SupervisoryAndRecallCommands from commandSupervisionAct::supervisionOutA to commandSupervision::supervisionIn;
        flow supervisionToBFlow of Common::SupervisoryAndRecallCommands from commandSupervisionAct::supervisionOutB to commandSupervision::supervisionIn;
        flow recallToAFlow of Common::SupervisoryAndRecallCommands from recallAndLandAct::recallOutA to recallAndLand::recallIn;
        flow recallToBFlow of Common::SupervisoryAndRecallCommands from recallAndLandAct::recallOutB to recallAndLand::recallIn;
        flow ackToAFlow of Common::ReportAcknowledgements from acknowledgeReportAct::ackOut to reportDetections::ackIn;
        flow ackToSystemFlow of Common::ReportAcknowledgements from acknowledgeReportAct::ackOut to acknowledgeReport::ackIn;
        flow statusAFlow of Common::StatusPicture from presentStatusPicture::statusOut to viewStatusAct::statusInA;
        flow statusBFlow of Common::StatusPicture from presentStatusPicture::statusOut to viewStatusAct::statusInB;
        flow reportsAFlow of Common::DetectionReportsAndTracks from reportDetections::reportsOut to mergeAct::swarmReportsInA;
        flow reportsBFlow of Common::DetectionReportsAndTracks from reportDetections::reportsOut to mergeAct::swarmReportsInB;
        flow decisionsAFlow of Common::DecisionRecords from recordDecision::decisionsOut to mergeAct::decisionRecordsInA;
        flow decisionsBFlow of Common::DecisionRecords from recordDecision::decisionsOut to mergeAct::decisionRecordsInB;
        flow cameraTracksFlow of Common::CameraNetworkTracks from provideCameraTracksAct::cameraTracksOut to mergeAct::cameraTracksIn;
        flow mergedToAnalystsFlow of Common::DetectionReportsAndTracks from mergeAct::mergedOut to judgeAlertsAct::mergedIn;
        flow handOverSectorFlow of Common::CoordinationMessage from handOverSector::msgOut to handOverSector::msgIn;
        flow rotateRechargeFlow of Common::CoordinationMessage from rotateRecharge::msgOut to rotateRecharge::msgIn;
        flow rechargeRequestFlow of Common::CoordinationMessage from rotateRecharge::msgOut to serviceAndRechargeAct::rechargeIn;
        flow redistributeCoverageFlow of Common::CoordinationMessage from redistributeCoverage::msgOut to redistributeCoverage::msgIn;
        flow deconflictMembersFlow of Common::CoordinationMessage from deconflictMembers::msgOut to deconflictMembers::msgIn;
        flow relayLinkFlow of Common::CoordinationMessage from relayLink::msgOut to relayLink::msgIn;
        flow correlateTracksFlow of Common::Track from correlateTracks::trackOut to correlateTracks::trackIn;
        flow handOverTrackFlow of Common::Track from handOverTrack::trackOut to handOverTrack::trackIn;
        flow admitMemberFlow of Common::CoordinationMessage from admitMember::msgOut to admitMember::msgIn;

        // hazards stated at SA are satisfied here by path, never restated (CV-19/safety option)
        satisfy SurveillanceDroneSwarm::SA::Hazards::PositionDriftHazard by navigateAgainstStoredMaps;
        satisfy SurveillanceDroneSwarm::SA::Hazards::MeshJammingHazard by relayLink;
        satisfy SurveillanceDroneSwarm::SA::Hazards::MisclassificationHazard by detectAndClassifyObjects;
        satisfy SurveillanceDroneSwarm::SA::Hazards::SensingDegradedUnnoticedHazard by presentStatusPicture;
        satisfy SurveillanceDroneSwarm::SA::Hazards::StaleTrackHazard by correlateTracks;
        satisfy SurveillanceDroneSwarm::SA::Hazards::SpoofedMemberHazard by admitMember;
        satisfy SurveillanceDroneSwarm::SA::Hazards::MixedClassifierVersionsHazard by manageClassifierVersion;
        satisfy SurveillanceDroneSwarm::SA::Hazards::OperatorOverloadHazard by reportDetections;

        // hazards this layer adds, visible once the population's member definition exchanges over a peer mesh
        package Hazards {
            doc /* hazards added at LA: risks that become visible once the population's member definition (SurveillanceDrone, above) is instantiated as members exchanging over a peer mesh link and the functions above are allocated to the placeholder logical component. Each is satisfied below by the coordination function that mitigates it. */

            #Hazard requirement MemberCollisionHazard {
                subject s : SurveillanceDroneSwarm::LA::SurveillanceDrone;
                doc /* two members sharing the same airspace fail to deconflict their flight paths and risk collision. */
            }
            #Hazard requirement PrematureDepartureHazard {
                subject s : SurveillanceDroneSwarm::LA::SurveillanceDrone;
                doc /* a member leaves its sector for recall or recharge before a handover to a peer completes, leaving a gap in watch. */
            }
            #Hazard requirement UncoveredMemberLossHazard {
                subject s : SurveillanceDroneSwarm::LA::SurveillanceDrone;
                doc /* a member is lost or grounded and the fleet does not redistribute coverage quickly enough, leaving its sector unwatched. */
            }
            #Hazard requirement UnrelayedIsolationHazard {
                subject s : SurveillanceDroneSwarm::LA::SurveillanceDrone;
                doc /* an isolated member finds no peer able to relay for it and drops out of coordination without anyone noticing. */
            }
        }
        satisfy Hazards::MemberCollisionHazard by deconflictMembers;
        satisfy Hazards::PrematureDepartureHazard by handOverSector;
        satisfy Hazards::UncoveredMemberLossHazard by redistributeCoverage;
        satisfy Hazards::UnrelayedIsolationHazard by relayLink;

        // ── architecture, alternative 2 ──
        // ===== LA alternative 2 of 2: decentralized swarm coordination, thin ground gateway =====
        // Genuinely different split from alternative 1: alternative 1 keeps the deciding
        // #Coordination on the ground; this alternative settles ALL eight #Coordination
        // functions onboard, over the mesh, among the members themselves (>= half, per the
        // house rule, is satisfied at 8/8). The five #C2 functions keep a ground usage here
        // too, hosted on one logical ground component, so a human still tasks, supervises,
        // recalls and is shown status and acknowledges reports from one place.

        #Member part def SurveillanceDrone {
          doc /* the replicable member of the twelve-drone population, as realised at LA-2: one surveillance drone carrying its own watch, sensing, navigation, coordination and reporting functions, and the ports it needs to reach its peers over the mesh and the ground station over the ground link. Coordinator choice: at any time the member with the lowest platform id among those currently reachable over the mesh acts as sector-handover/redistribution coordinator for its reachable group; every member runs the same election rule, so any reachable member can take over instantly if the incumbent drops off the mesh -- no ground confirmation is needed to replace it, and a healed partition re-elects by the same rule. When the ground link drops, onboard coordination (handOverSector, rotateRecharge, redistributeCoverage, deconflictMembers, relayLink, correlateTracks, handOverTrack, admitMember) continues unchanged, since none of it depends on groundStation; only new tasking, the operator's view of status and acknowledgement are delayed until the link returns. When groundStation itself fails, the fleet keeps watching and coordinating on the same onboard basis indefinitely, but no new tasking, supervision or recall can reach it until a ground station is restored. */

          out port meshOut : Common::MeshPort {
            doc /* transmits coordination and relay traffic to a peer drone over the mesh radio. */
          }
          in port meshIn : ~Common::MeshPort {
            doc /* receives coordination and relay traffic from a peer drone over the mesh radio. */
          }
          in port taskingIn : Common::MissionTasking {
            doc /* takes in the area of interest, sectors and mission window relayed down from the ground station. */
          }
          in port commandIn : Common::SupervisoryAndRecallCommands {
            doc /* takes in priorities, the sector to look at more closely and the reporting threshold, relayed down from the ground station. */
          }
          in port recallIn : Common::SupervisoryAndRecallCommands {
            doc /* takes in a recall-and-land order for the fleet or for this drone, relayed down from the ground station. */
          }
          out port reportsOut : Common::DetectionReportsAndTracks {
            doc /* sends this drone's triaged, de-duplicated detection reports and tracks toward the ground station. */
          }
          out port decisionsOut : Common::DecisionRecords {
            doc /* sends the decision record for every report this drone has sent toward the ground station. */
          }
          out port statusOut : Common::StatusPicture {
            doc /* sends this drone's position, activity, coverage and degradation toward the ground station's status picture. */
          }
          out port rechargeRequestOut : Common::CoordinationMessage {
            doc /* sends a recharge-slot request, negotiated onboard by rotateRecharge, toward the ground station and on to the ground crew. */
          }

          #Mode state def MemberMode {
            doc /* the operating mode of one member drone in LA-2, nested inside the #Member part def itself so the brief's named modes are states of SurveillanceDrone's own machine; carries the rules the system never breaks. */

            initial start;
            transition start -> Landed;

            state Landed {
              doc /* grounded, not watching: recalled, out of cleared airspace, quarantined, or recharging. */
            }
            state Watching {
              doc /* actively holding assigned sector watch under normal conditions. */
            }
            state NavigationDegraded {
              doc /* the brief's named mode: no satellite positioning; navigating by matching camera views against stored maps. */
            }
            state SensingDegraded {
              doc /* the brief's named mode: this drone's sensors cannot be trusted as they are. */
            }
            state Isolated {
              doc /* the brief's named mode: cut off from the other drones. */
            }
            state Quarantined {
              doc /* the brief's named mode: failed admission; takes no part in coordination until readmitted. */
            }
            state Recalled {
              doc /* under a recall-and-land order; no longer watching, heading to land. */
            }
            state OutsideClearedAirspace {
              doc /* outside the airspace authority's cleared limits; no longer watching, heading to land. */
            }

            transition Landed -> Watching;
            transition Watching -> NavigationDegraded;
            transition NavigationDegraded -> Watching;
            transition Watching -> SensingDegraded;
            transition SensingDegraded -> Watching;
            transition Watching -> Isolated;
            transition Isolated -> Watching;
            transition Isolated -> Landed;
            transition Watching -> Recalled;
            transition NavigationDegraded -> Recalled;
            transition SensingDegraded -> Recalled;
            transition Isolated -> Recalled;
            transition Recalled -> Landed;
            transition Watching -> OutsideClearedAirspace;
            transition OutsideClearedAirspace -> Landed;
            transition Watching -> Quarantined;
            transition Quarantined -> Landed;

            @SysproseVerification::PropertyPattern {
              doc /* RecallWins: once a drone is recalled, it does not watch again until it has landed. */
              attribute pattern = "absence";
              attribute scope = "between";
              attribute q = "state Recalled";
              attribute r = "state Landed";
              attribute p = "state Watching";
            }
            @SysproseVerification::PropertyPattern {
              doc /* ReturnsWhenIsolated: from any situation a drone can be in, it can always get back to landed; an isolated drone included. */
              attribute pattern = "recovery";
              attribute scope = "globally";
              attribute p = "state Landed";
            }
            @SysproseVerification::PropertyPattern {
              doc /* GeofenceBreachEndsWatch: once a drone is outside its cleared airspace, it does not watch until it has landed. */
              attribute pattern = "absence";
              attribute scope = "between";
              attribute q = "state OutsideClearedAirspace";
              attribute r = "state Landed";
              attribute p = "state Watching";
            }
            @SysproseVerification::PropertyPattern {
              doc /* QuarantinedStaysOut: once a drone is quarantined, it takes no part in coordination until it has been readmitted. */
              attribute pattern = "absence";
              attribute scope = "between";
              attribute q = "state Quarantined";
              attribute r = "state Landed";
              attribute p = "state Watching";
            }
          }

          #State state def MemberState {
            doc /* the coarse platform status of one member drone, independent of its watch mode, nested inside the #Member part def. */
            initial start;
            transition start -> Idle;
            state Idle {
              doc /* on the ground, available but not tasked. */
            }
            state Active {
              doc /* airborne and performing tasked activity. */
            }
            state Recharging {
              doc /* at a recharge point being serviced by the ground crew. */
            }
            transition Idle -> Active;
            transition Active -> Recharging;
            transition Recharging -> Idle;
            transition Active -> Idle;
          }

          state mode : MemberMode {
            doc /* this drone's operating mode: watching, degraded, isolated, quarantined, recalled, outside cleared airspace, or landed. */
          }
          state platformStatus : MemberState {
            doc /* this drone's coarse platform status: idle, active or recharging. */
          }
        }
        part fleet : SurveillanceDrone [12] {
          doc /* the twelve-member fleet: every member performs the watch, sensing, navigation, reporting and all eight coordination functions of this architecture. */
          state configuration : FleetConfiguration {
            doc /* the fleet-level watch configuration: normal coverage or mesh-degraded (the brief's named MeshDegraded fleet mode). */
          }
        }
        part memberA : SurveillanceDrone {
          doc /* first representative member, used to show the pairwise mesh interaction pattern between peers. */
        }
        part memberB : SurveillanceDrone {
          doc /* second representative member, used to show the pairwise mesh interaction pattern between peers. */
        }
        interface peerLink : Common::MeshLink connect memberA.meshOut to memberB.meshIn {
          doc /* the mandated peer link between the two representative members: memberA's coordination traffic reaching memberB. */
        }
        interface peerLinkReturn : Common::MeshLink connect memberB.meshOut to memberA.meshIn {
          doc /* the return leg of the peer link: memberB's coordination traffic reaching memberA. */
        }
        interface fleetMeshDown : Common::MeshLink connect fleet.meshOut to memberA.meshIn {
          doc /* the rest of the fleet's mesh traffic reaching memberA, closing the ring so every mesh port is used. */
        }
        interface fleetMeshUp : Common::MeshLink connect memberB.meshOut to fleet.meshIn {
          doc /* memberB's mesh traffic reaching the rest of the fleet, closing the ring so every mesh port is used. */
        }
        part def GroundStation {
          doc /* the single logical ground-side component of LA-2: a thin gateway that hosts all five command-and-control functions and classifier version management, and relays tasking, supervision, recall, reports, decisions, status and recharge requests between the operations centre, duty controller, ground crew and the fleet. It does not do any of the eight coordination functions, which are settled entirely onboard in this architecture. */

          in port taskingInExt : Common::MissionTasking {
            doc /* takes in mission tasking from the operations centre. */
          }
          in port commandInExt : Common::SupervisoryAndRecallCommands {
            doc /* takes in supervisory commands from the duty controller. */
          }
          in port recallInExt : Common::SupervisoryAndRecallCommands {
            doc /* takes in a recall-and-land order from the duty controller. */
          }
          in port ackInExt : Common::ReportAcknowledgements {
            doc /* takes in the duty controller's acknowledgement of a detection report. */
          }
          out port reportsOutExt : Common::DetectionReportsAndTracks {
            doc /* sends triaged, de-duplicated reports and tracks to the operations centre. */
          }
          out port decisionsOutExt : Common::DecisionRecords {
            doc /* sends decision records to the operations centre. */
          }
          out port statusOutExt : Common::StatusPicture {
            doc /* sends the assembled fleet status picture to the duty controller. */
          }
          out port rechargeOutExt : Common::CoordinationMessage {
            doc /* sends a recharge-slot request to the ground crew. */
          }

          out port taskingOutFleet : Common::MissionTasking {
            doc /* relays mission tasking down to the fleet. */
          }
          out port commandOutFleet : Common::SupervisoryAndRecallCommands {
            doc /* relays supervisory commands down to the fleet. */
          }
          out port recallOutFleet : Common::SupervisoryAndRecallCommands {
            doc /* relays a recall-and-land order down to the fleet. */
          }
          in port reportsInFleet : Common::DetectionReportsAndTracks {
            doc /* takes in detection reports and tracks from the fleet. */
          }
          in port decisionsInFleet : Common::DecisionRecords {
            doc /* takes in decision records from the fleet. */
          }
          in port statusInFleet : Common::StatusPicture {
            doc /* takes in each member's contribution to the status picture. */
          }
          in port rechargeInFleet : Common::CoordinationMessage {
            doc /* takes in recharge-slot requests from the fleet. */
          }
        }
        part groundStation : GroundStation {
          doc /* the one instance of the ground gateway in LA-2. */
          state mode : GroundStationMode {
            doc /* the ground station's own operating mode. */
          }
          state platformStatus : GroundStationStatus {
            doc /* the ground station's coarse platform status. */
          }
        }
        #Mode state def GroundStationMode {
          doc /* the ground station's operating mode: linked to the fleet under normal conditions, or degraded when the ground link itself is down. In this architecture the fleet keeps watching regardless, since coordination does not depend on this link. */
          initial start;
          transition start -> Linked;
          state Linked {
            doc /* the ground link to the fleet is up. */
          }
          state LinkDegraded {
            doc /* the ground link to the fleet, the operations centre or the duty controller is down or degraded. */
          }
          transition Linked -> LinkDegraded;
          transition LinkDegraded -> Linked;
        }
        #State state def GroundStationStatus {
          doc /* the coarse platform status of the ground station. */
          initial start;
          transition start -> Idle;
          state Idle {
            doc /* no active mission tasking is being relayed. */
          }
          state Active {
            doc /* mission tasking is active and the gateway is relaying reports, decisions and status. */
          }
          transition Idle -> Active;
          transition Active -> Idle;
        }
        // ----- ground-fleet relay connections: each of the fleet's three usages (fleet,
        // memberA, memberB) is wired so no port is left dangling. -----

        connection taskingDown_fleet connect groundStation.taskingOutFleet to fleet.taskingIn {
          doc /* relays mission tasking to the fleet. */
        }
        connection taskingDown_A connect groundStation.taskingOutFleet to memberA.taskingIn {
          doc /* relays mission tasking to memberA. */
        }
        connection taskingDown_B connect groundStation.taskingOutFleet to memberB.taskingIn {
          doc /* relays mission tasking to memberB. */
        }
        connection commandDown_fleet connect groundStation.commandOutFleet to fleet.commandIn {
          doc /* relays supervisory commands to the fleet. */
        }
        connection commandDown_A connect groundStation.commandOutFleet to memberA.commandIn {
          doc /* relays supervisory commands to memberA. */
        }
        connection commandDown_B connect groundStation.commandOutFleet to memberB.commandIn {
          doc /* relays supervisory commands to memberB. */
        }
        connection recallDown_fleet connect groundStation.recallOutFleet to fleet.recallIn {
          doc /* relays a recall-and-land order to the fleet. */
        }
        connection recallDown_A connect groundStation.recallOutFleet to memberA.recallIn {
          doc /* relays a recall-and-land order to memberA. */
        }
        connection recallDown_B connect groundStation.recallOutFleet to memberB.recallIn {
          doc /* relays a recall-and-land order to memberB. */
        }
        connection reportsUp_fleet connect fleet.reportsOut to groundStation.reportsInFleet {
          doc /* the fleet's detection reports and tracks reaching the ground station. */
        }
        connection reportsUp_A connect memberA.reportsOut to groundStation.reportsInFleet {
          doc /* memberA's detection reports and tracks reaching the ground station. */
        }
        connection reportsUp_B connect memberB.reportsOut to groundStation.reportsInFleet {
          doc /* memberB's detection reports and tracks reaching the ground station. */
        }
        connection decisionsUp_fleet connect fleet.decisionsOut to groundStation.decisionsInFleet {
          doc /* the fleet's decision records reaching the ground station. */
        }
        connection decisionsUp_A connect memberA.decisionsOut to groundStation.decisionsInFleet {
          doc /* memberA's decision records reaching the ground station. */
        }
        connection decisionsUp_B connect memberB.decisionsOut to groundStation.decisionsInFleet {
          doc /* memberB's decision records reaching the ground station. */
        }
        connection statusUp_fleet connect fleet.statusOut to groundStation.statusInFleet {
          doc /* the fleet's status contribution reaching the ground station. */
        }
        connection statusUp_A connect memberA.statusOut to groundStation.statusInFleet {
          doc /* memberA's status contribution reaching the ground station. */
        }
        connection statusUp_B connect memberB.statusOut to groundStation.statusInFleet {
          doc /* memberB's status contribution reaching the ground station. */
        }
        connection rechargeUp_fleet connect fleet.rechargeRequestOut to groundStation.rechargeInFleet {
          doc /* the fleet's recharge-slot requests reaching the ground station. */
        }
        connection rechargeUp_A connect memberA.rechargeRequestOut to groundStation.rechargeInFleet {
          doc /* memberA's recharge-slot requests reaching the ground station. */
        }
        connection rechargeUp_B connect memberB.rechargeRequestOut to groundStation.rechargeInFleet {
          doc /* memberB's recharge-slot requests reaching the ground station. */
        }
        // ----- ground station to the SA-level actors (upward references; never restated) -----

        connection taskingFromOpsCentre connect SurveillanceDroneSwarm::SA::operationsCentre.taskingOut to groundStation.taskingInExt {
          doc /* mission tasking arriving from the operations centre. */
        }
        connection commandFromDutyController connect SurveillanceDroneSwarm::SA::dutyController.supervisionOut to groundStation.commandInExt {
          doc /* supervisory commands arriving from the duty controller. */
        }
        connection recallFromDutyController connect SurveillanceDroneSwarm::SA::dutyController.recallOut to groundStation.recallInExt {
          doc /* recall-and-land orders arriving from the duty controller. */
        }
        connection ackFromDutyController connect SurveillanceDroneSwarm::SA::dutyController.ackOut to groundStation.ackInExt {
          doc /* report acknowledgements arriving from the duty controller. */
        }
        connection reportsToOpsCentre connect groundStation.reportsOutExt to SurveillanceDroneSwarm::SA::operationsCentre.reportsIn {
          doc /* triaged reports and tracks sent to the operations centre. */
        }
        connection decisionsToOpsCentre connect groundStation.decisionsOutExt to SurveillanceDroneSwarm::SA::operationsCentre.decisionsIn {
          doc /* decision records sent to the operations centre. */
        }
        connection statusToDutyController connect groundStation.statusOutExt to SurveillanceDroneSwarm::SA::dutyController.statusIn {
          doc /* the fleet status picture sent to the duty controller. */
        }
        connection rechargeToGroundCrew connect groundStation.rechargeOutExt to SurveillanceDroneSwarm::SA::groundCrew.rechargeIn {
          doc /* recharge-slot requests sent to the ground crew. */
        }
        // ----- allocation: every SA function realised by exactly one LA component -----
        // on-board (fleet): the five base watch/report functions plus all eight
        // #Coordination functions -- the alternative-2 decision. Bare names: these
        // allocate the local action usages of this document, not the SA layer's.
        allocate holdSectorWatch to fleet;
        allocate detectAndClassifyObjects to fleet;
        allocate navigateAgainstStoredMaps to fleet;
        allocate reportDetections to fleet;
        allocate recordDecision to fleet;
        allocate handOverSector to fleet;
        allocate rotateRecharge to fleet;
        allocate redistributeCoverage to fleet;
        allocate deconflictMembers to fleet;
        allocate relayLink to fleet;
        allocate correlateTracks to fleet;
        allocate handOverTrack to fleet;
        allocate admitMember to fleet;
        // ground (groundStation): all five #C2 functions keep a ground usage, plus
        // classifier version management held centrally to avoid mixed versions.
        allocate taskMission to groundStation;
        allocate commandSupervision to groundStation;
        allocate recallAndLand to groundStation;
        allocate presentStatusPicture to groundStation;
        allocate acknowledgeReport to groundStation;
        allocate manageClassifierVersion to groundStation;
        // ----- rules the system never breaks (CV-18): carried on the member's machine -----
        satisfy SurveillanceDroneSwarm::SA::RecallWins by fleet;
        satisfy SurveillanceDroneSwarm::SA::ReturnsWhenIsolated by fleet;
        satisfy SurveillanceDroneSwarm::SA::GeofenceBreachEndsWatch by fleet;
        satisfy SurveillanceDroneSwarm::SA::QuarantinedStaysOut by fleet;
        // ----- hazards stated at SA: satisfied here by path, never restated -----
        satisfy SurveillanceDroneSwarm::SA::Hazards::PositionDriftHazard by fleet;
        satisfy SurveillanceDroneSwarm::SA::Hazards::MeshJammingHazard by fleet;
        satisfy SurveillanceDroneSwarm::SA::Hazards::MisclassificationHazard by fleet;
        satisfy SurveillanceDroneSwarm::SA::Hazards::SensingDegradedUnnoticedHazard by groundStation;
        satisfy SurveillanceDroneSwarm::SA::Hazards::StaleTrackHazard by fleet;
        satisfy SurveillanceDroneSwarm::SA::Hazards::SpoofedMemberHazard by fleet;
        satisfy SurveillanceDroneSwarm::SA::Hazards::MixedClassifierVersionsHazard by groundStation;
        satisfy SurveillanceDroneSwarm::SA::Hazards::OperatorOverloadHazard by groundStation;
        // ----- hazards stated at LA (by the other alternative's section): satisfied here
        // too, by THIS architecture's own components, since a hazard satisfied only by a
        // shared function does not count for this alternative. Never restated. -----
        satisfy SurveillanceDroneSwarm::LA::Hazards::MemberCollisionHazard by fleet;
        satisfy SurveillanceDroneSwarm::LA::Hazards::PrematureDepartureHazard by fleet;
        satisfy SurveillanceDroneSwarm::LA::Hazards::UncoveredMemberLossHazard by fleet;
        satisfy SurveillanceDroneSwarm::LA::Hazards::UnrelayedIsolationHazard by fleet;
        // ----- hazards LA-2 adds: risks specific to settling all eight coordination
        // functions onboard the mesh without a ground arbiter, not yet covered above -----
        package HazardsLA2 {
          doc /* hazards this architecture adds by moving all eight coordination functions onboard the mesh, where the hazards stated above do not yet cover the consequences of that specific placement decision. */

          #Hazard requirement CoordinationForkHazard {
            doc /* under heavy jamming the mesh can partition into two groups; each half, deciding sector handover and redistribution onboard without a ground arbiter, can independently reassign the same sector, and neither half can see the other's claim until the partition heals. */
            subject s : SurveillanceDroneSwarm::LA::SurveillanceDrone;
          }
          #Hazard requirement GroundBlindSpotHazard {
            doc /* because coordination decisions are settled onboard without waiting for ground confirmation, the status picture assembled at the ground station can lag the fleet's true onboard state during a mesh degradation, hiding a genuine coverage gap from the duty controller until the next status update arrives. */
            subject s : SurveillanceDroneSwarm::LA::GroundStation;
          }
        }
        satisfy HazardsLA2::CoordinationForkHazard by fleet;
        satisfy HazardsLA2::GroundBlindSpotHazard by groundStation;
        // ----- measures of effectiveness: LA-2's own worst-case estimate, with basis -----
        #Estimate attribute areaUnderWatchShare :> Common::areaUnderWatchShare = 0.92 {
          doc /* basis: SA requires >= 0.9. Onboard handOverSector and redistributeCoverage let the fleet re-spread within one mesh exchange instead of waiting on a ground decision, so LA-2's worst case sits above the SA floor. */
        }
        #Estimate attribute coverageLossOnMemberLoss :> Common::coverageLossOnMemberLoss = 0.18 {
          doc /* basis: brief allows <= 0.25. redistributeCoverage runs onboard the instant a member drops off the mesh, without waiting for a ground link round trip, so the loss before re-spread is smaller than a ground-arbitrated redistribution would allow. */
        }
        #Estimate attribute jammedMeshAreaUnderWatchShare :> Common::jammedMeshAreaUnderWatchShare = 0.78 {
          doc /* basis: brief requires >= 0.75. With half the links jammed, relayLink and deconflictMembers run entirely onboard among whichever members can still reach each other, so watch continues without needing the ground link at all; the remaining loss comes from the partitions relayLink cannot bridge. */
        }
        #Estimate attribute groundLinkLossAreaUnderWatchShare :> Common::groundLinkLossAreaUnderWatchShare = 0.92 {
          doc /* basis: target set here at 0.9, the brief's continuous-watch figure. This is LA-2's defining strength: none of the eight coordination functions depend on the ground link, so losing groundStation's uplink to the fleet does not stall handovers, rotation or redistribution -- only presentStatusPicture, acknowledgement and new tasking are delayed. */
        }
        #Estimate attribute watchEnduranceHours :> Common::watchEnduranceHours = 30 {
          doc /* basis: target set here at >= 24 h. rotateRecharge, settled onboard, keeps the fleet's 40-minute-flight/60-minute-recharge cycle running without a ground scheduler in the loop, so endurance is bounded by the ground crew's servicing rate rather than by link availability. */
        }
        #Estimate attribute reportLatencySeconds :> Common::reportLatencySeconds = 50 {
          doc /* basis: brief allows <= 60 s with the link up. correlateTracks runs onboard before a report leaves the fleet, adding a small onboard triage step ahead of the single ground-link hop through groundStation to the operations centre. */
        }
        #Estimate attribute positionErrorWithoutGnssMeters :> Common::positionErrorWithoutGnssMeters = 42 {
          doc /* basis: brief allows <= 50 m after 10 minutes without satellite positioning. navigateAgainstStoredMaps, onboard on every member, matches camera views against stored maps regardless of mesh or ground-link state, so the drift estimate does not change with coordination placement. */
        }
        #Estimate attribute reportHoldMinutes :> Common::reportHoldMinutes = 34 {
          doc /* basis: brief requires >= 30 min. reportDetections holds a member's reports onboard whenever groundStation's uplink is down; since coordination and sector watch continue independently of the ground link in LA-2, a cut-off member keeps flying and holding rather than landing early, giving slightly more hold time than a design that needs the ground link for coordination. */
        }
        #Estimate attribute reportsLostInLinkGap :> Common::reportsLostInLinkGap = 0 {
          doc /* basis: brief says none. reportDetections and recordDecision, both onboard, queue reports and their decision records until groundStation's uplink returns; nothing is discarded because none of the onboard functions require the ground link to keep running. */
        }
        #Estimate attribute missedDetectionShare :> Common::missedDetectionShare = 0.08 {
          doc /* basis: brief allows <= 0.1. detectAndClassifyObjects runs onboard on every member regardless of mesh or ground-link condition; the only degradation this architecture adds is the rare coordination fork during a mesh partition (CoordinationForkHazard), which can leave a sliver of a sector briefly unwatched. */
        }
        #Estimate attribute falseAlarmsPerHour :> Common::falseAlarmsPerHour = 1.6 {
          doc /* basis: brief allows <= 2/h. correlateTracks and handOverTrack, both onboard, de-duplicate and drop stale tracks before a report ever reaches groundStation, so the ground-side gate sees fewer spurious alerts than an unfiltered feed would produce. */
        }
        #Estimate attribute operatorAlertsPerHour :> Common::operatorAlertsPerHour = 17 {
          doc /* basis: the operator can judge at most 20/h. groundStation, hosting presentStatusPicture and acknowledgeReport, is the single gate the operator sees; with onboard correlation already thinning duplicates, the worst-case rate stays under the cap with headroom. */
        }
        #Estimate attribute acknowledgedReportsThatMatterShare :> Common::acknowledgedReportsThatMatterShare = 0.81 {
          doc /* basis: brief requires >= 0.8. onboard triage in reportDetections and correlateTracks removes low-confidence duplicates before groundStation ever shows them to the duty controller, keeping the acknowledged set weighted toward reports that matter. */
        }
        #Estimate attribute onboardClassificationCostUsd :> Common::onboardClassificationCostUsd = 285 {
          doc /* basis: brief allows <= 300 USD per drone. detectAndClassifyObjects runs fully onboard every member (as it must, to keep watching through a link or mesh gap), which is the most compute-hungry placement this cap has to cover; 285 USD leaves headroom under the cap. */
        }
        #prose part laTradeOff {
        doc /* Architecture trade-off for LA. Alternative 2 was taken.
                 alternative 1: total 0.67 (measures 0.86, review 0.28, structure 0.78, resilience 0.19)
                 alternative 2: total 0.90 (measures 1.00, review 0.56, structure 0.84, resilience 0.63)
                 The measures term scores the worst case of each alternative's own #Estimate: claims its architecture states with their basis, not measurements.
                 I would take Alternative 2. Alternative 1 puts every deciding coordination function on groundControlStation, including deconflictMembers and relayLink, which only make sense on the mesh. The result is a ground-hosted catch-all component. The model's own documentation says coordination stops fleet-wide on link or station loss, and that members fly their last directive (localFallbackOnIsolation) with no controlled landing. It accepts that single point of failure as a hazard and misses two targets: groundLinkLoss 0.55 and endurance 20 h. Alternative 2 moves all eight coordination functions onto SurveillanceDrone, with a lowest-id coordinator election, and reduces GroundStation to a gateway for C2 and classifier versions. Coordination, correlation and report holding therefore survive a lost link. Its weaknesses are real and should be fixed at the next layer. The member is overloaded, and the four rules sit on the same MemberMode that detects and coordinates, with no independent monitor. If the ground station fails, the fleet keeps flying with no recall path and no landing policy. Recharge requests reach the ground crew only through groundStation, so the claims of 0.92 coverage with the ground down and 30 h endurance are overstated. coverageLossOnMemberLoss 0.18 is below the duty-cycle floor of about 0.21 and has no mechanism behind it. The two new hazards are 'satisfied' by the components that cause them, and the triple wiring (fleet, memberA, memberB) plus the ring 'so every mesh port is used' pads the model without adding architecture. Even so, Alternative 2's split of responsibilities is the one that survives the next layer. */
        }
    }
